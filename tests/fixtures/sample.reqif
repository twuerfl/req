# Sample Fixture

## HLR-FIXTURE-01: Fixture High-Level Requirement (HLR)
A high-level requirement for testing.
- Status: approved

## LLR-FIXTURE-01: Fixture Low-Level Requirement (LLR)
A low-level requirement for testing.
- Status: draft
